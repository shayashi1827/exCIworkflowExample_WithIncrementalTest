# Req_DoorLockCntr

## req01: ドアロック・アンロック指令 (Functional)
車両の状態に応じて自動でドアをロック/アンロックしてほしい。
ロック条件
車両が走行状態になった場合に、ドアのロック指令を出力してほしい
・「車両速度 >= 5km」が2秒間以上継続した場合に車両走行状態と判断する
・「エンジン始動状態 かつ 車両走行状態」成立時にロック要求指令を出力する
アンロック条件
車両に異常が発生した場合に、ドアのアンロック指令を出力してほしい
・エアバッグ作動した場合、ドアのアンロック指令を出力する

## req02: ドアロック位置算出 (Functional)
作動位置によってロックポジションを以下のように判定する。
・valが4mm以上 ⇒ ロック状態
・valが1mm以下 ⇒ アンロック状態
・上記以外 ⇒ ニュートラル状態

## req03: ドアロック状態判定 (Functional)
以下の表に応じて診断結果を判定する。
| 制御指令 | ロック位置 | 判定 |
| --- | --- | --- |
| ロック | ロック | OK |
|  | ロック以外 | NG |
| アンロック | アンロック | OK |
|  | アンロック以外 | NG |

## req04: ドアロック異常診断 (Functional)
ドアロック機構に何らかの異常がある場合、故障と判断し、ダイアグ信号要求を出力してほしい
診断タイミング
ドアロック指令の変化から2秒後の時点とする
その他
一度、故障と診断された後は再度ダイアグ判定を行わない
